(defun c:beamdet ()
  (setq restoreosmode (getvar "osmode"))
   (setvar "INSUNITS" 4)
  (setq beamnum (getint "How many beams in total?"))
   (setq a 1)
   (while (<= a beamnum)
  (alert "Select the end points of the beam")
  (setq p1 (getpoint "Select the starting point of the beam"))
  (setq p2 (getpoint "Select the end point of the beam"))
  (setq span (distance p1 p2))
  (princ span)
  (setvar "osmode" 0)
  (setq layername1 "Beamdetails")
  (setq layercolor1 "255")
  (setq layername2 "Beamsteel")
  (setq layercolor2 "6")
  (setq d (getdist "Enter the depth of the beam"))
  (setq b1 (getpoint "Pick a point outside"))
  (setq	x1 (car b1)
	x2 (+ x1 span)
	y1 (cadr b1)
	y2 (+ y1 d)
  )
  (setq	b2 (list x2 y1 0.0)
	b3 (list x2 y2 0.0)
	b4 (list x1 y2 0.0)
  )
  (command ".layer" "n"	layername1 "C" layercolor1 layername1 "")
  (command ".chprop" (entlast) "" "la" layername1 "")
  (command "line" b1 b2 "")
  (command "line" b2 b3 "")
  (command "line" b3 b4 "")
  (command "line" b4 b1 "")
  (setq c (float (getdist "Enter the cover for steel")))
  (command ".layer" "n" layername2 "C" layercolor2 layername2 "")
  (command "line"
	   (mapcar '+ b1 (list c c 0.0))
	   (mapcar '+ b2 (list (- c) c 0.0))
	   ""
  )
  (command ".chprop" (entlast) "" "la" layername2 "")
  (command "line"
	   (mapcar '+ b2 (list (- c) c 0.0))
	   (mapcar '+ b3 (list (- c) (- c) 0.0))
	   ""
  )
   (command ".chprop" (entlast) "" "la" layername2 "")
  (command "line"
	   (mapcar '+ b3 (list (- c) (- c) 0.0))
	   (mapcar '+ b4 (list c (- c) 0.0))
	   ""
  )
   (command ".chprop" (entlast) "" "la" layername2 "")
  (command "line"
	   (mapcar '+ b4 (list c (- c) 0.0))
	   (mapcar '+ b1 (list c c 0.0))
	   ""
  )
   (command ".chprop" (entlast) "" "la" layername2 "")
  (setq col (getint "How many column cross this beam?"))
  (setq i 1)
  (setq sp (list))
  (while (<= i col)
    (alert "Select the end points of the columns in the beam")
    (setq cx1 (getpoint "Select the beginning of the column"))
    (setq cx2 (getpoint "Select the end point of the column"))
    (setq dis1 (- (car cx1) (car p1)))
    (setq dis2 (- (car cx2) (car cx1)))
    (setq bx1 (mapcar '+ b1 (list dis1 0.0 0.0)))
    (setq bx2 (mapcar '+ bx1 (list dis2 0.0 0.0)))
    (command "line"
	     (mapcar '- bx1 (list 0.0 (* d 5) 0.0))
	     (mapcar '+ bx1 (list 0.0 (* d 5) 0.0))
	     ""
    )
    (command "line"
	     (mapcar '- bx2 (list 0.0 (* d 5) 0.0))
	     (mapcar '+ bx2 (list 0.0 (* d 5) 0.0))
	     ""
    )
    (command "_layer" "n" layername1 "C" layercolor1 layername1 "")
    (setq drawing (getfiled "Select the reference drawing from the downloaded \"Beams Details\" file" "" "dwg" 16))
    (command "_.INSERT" drawing (mapcar '+ bx1 (list 0.0 (* d 5) 0.0)) "1" "1" "" "")
    (command-s)
    (command "_.INSERT" drawing (mapcar '+ bx1 (list 0.0 (* d -5) 0.0)) "1" "1" "" "")
    (command-s)
    (setq sp (append sp (list dis1 dis2)))
    (setq i (1+ i))
  )
  (princ sp)
  (if (> (nth 0 sp) 0)
    (progn
      (command "line" (mapcar '+ b1 (list (* 2 c) (* 2 c) 0.0))
	   (mapcar '+ b4 (list (* 2 c) (* 2 (- c)) 0.0))
	   ""
  )
      (command "line" (mapcar '+ b4 (list (* 2 c) (* 2 (- c)) 0.0))
	       (mapcar '+ b4 (list (* 2 c) (* 2 (- c)) 0.0) (list (* 0.33 (nth 0 sp)) 0.0 0.0))
      "")
    
)
    )
  (setq j 1)
  (while (<= j (length sp))
    (if (eq (rem j 2) 0)
      (progn
      (setq span1 (- (nth j sp) (nth (1- j) sp) (nth (- j 2) sp)))
      (setq span2 (- (nth (+ j 2) sp) (nth (1+ j) sp) (nth j sp)))
      (princ span1)
      (command "line" (mapcar '+ b4 (list (* 2 c) (* 2 (- c)) 0.0) (list (- span1 (* (qd:roundup (/ (* 0.33 span1) 1000) 0.25) 1000)) (* 2 (- c)) 0.0))
			      (mapcar '+ b4 (list (* 2 c) (* 2 (- c)) 0.0) (list (+ span2 (* (qd:roundup (/ (* 0.33 span2) 1000) 0.25) 1000)) (* 2 (- c)) 0.0))
			      "")
      (command "line" (mapcar '+ b4 (list (* 2 c) (* 2 (- c)) 0.0) (list (+ span1 (* (qd:rounddown (/ (* 0.15 span1) 1000) 0.25) 1000)) (* 2 (- c)) 0.0))
	       (mapcar '+ b4 (list (* 2 c) (* 2 (- c)) 0.0) (list (- span1 (* (qd:rounddown (/ (* 0.15 span1) 1000) 0.25) 1000)) (* 2 (- c)) 0.0))
	       "")     
	       
      )
      )
    (setq j (1+ j))
    )
     (command "line" (mapcar '+ b2 (list (* 2 (- c)) (* 2 c) 0.0))
	   (mapcar '+ b3 (list (* 2 (- c)) (* 2 (- c)) 0.0))
	   ""
  )
      (command "line" (mapcar '+ b3 (list (* 2 (- c)) (* 2 (- c)) 0.0))
	       (mapcar '+ b3 (list (* 2 c) (* 2 (- c)) 0.0) (list (- (* 0.33 (nth (- length sp) sp))) 0.0 0.0))
      "")
    
)
   (setq a (1+ a))
   )
   
      (defun qd:roundup ( n m )
  ((lambda ( r ) (cond ((equal 0.0 r 1e-8) n) ((< n 0) (- n r)) ((+ n (- m r))))) (rem n m))
  )
	       

(defun qd:rounddown ( n m)
  ((lambda ( r ) (cond ((equal 0.0 r 1e-8) n) ((< n 0) (- n r m)) ((- n r)))) (rem n m))
  )
